module sdo-first {
  /* This module only contains content changes to the sdo-first.yang module  */
  revision 2022-08-05;
  organization 'mef';
  namespace 'testing';
  prefix 'yang';

  leaf test-leaf {
    type string;
  }
}
